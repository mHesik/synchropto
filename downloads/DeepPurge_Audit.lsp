;;; =========================================================================
;;; ИНСТРУМЕНТ: DeepPurge_Audit.lsp
;;; НАЗНАЧЕНИЕ: Глубокая очистка чертежа от прокси-объектов, DGN-линий и мусора
;;; СОВМЕСТИМОСТЬ: AutoCAD 2018-2026, Civil 3D, nanoCAD
;;; РАЗРАБОТАНО ДЛЯ: СтройПТО.AI
;;; =========================================================================

(defun c:DEEPPURGE ( / )
  (vl-load-com)
  (princ "\n[СтройПТО.AI] Запуск глубокой оптимизации чертежа...")
  
  ;; Сброс масштабов аннотаций
  (setvar "CMDECHO" 0)
  (command "-scalelistedit" "reset" "y" "e")
  
  ;; Очистка DGN-типов линий
  (dictremove (namedobjdict) "ACAD_DGNLINESTYLECOMP")
  
  ;; Тройная рекурсивная очистка
  (repeat 3
    (vla-PurgeAll (vla-get-ActiveDocument (vlax-get-acad-object)))
  )
  
  ;; Проверка целостности базы данных чертежа
  (command "_audit" "y")
  
  (setvar "CMDECHO" 1)
  (princ "\n[СтройПТО.AI] Очистка успешно завершена! Размер файла оптимизирован.\n")
  (alert "СтройПТО.AI:\nГлубокая очистка чертежа выполнена!\nФайл оптимизирован, мусорные масштабы и неиспользуемые слои удалены.")
  (princ)
)

(princ "\n[СтройПТО.AI] Макрос DeepPurge_Audit загружен. Введите команду DEEPPURGE для запуска.\n")
